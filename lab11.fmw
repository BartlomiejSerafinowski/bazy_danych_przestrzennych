FME workspace lab11.fmw
Startup Python:
      import fme, smtplib, ssl
      from datetime
      import datetime

      mail = fme.macroValues['mail']
      haslo = fme.macroValues['haslo']
      powiat = fme.macroValues['powiat']
      mail2 = fme.macroValues['mail2']

      teraz = datetime.now()
      teraz_format = teraz.strftime("%d/%m/%Y %H:%M:%S")

      def wyslij(mail, mail2, wiadomosc ):
          # for SSL
          port = 465
          # SSL context
          context = ssl.create_default_context()

          with smtplib.SMTP_SSL("smtp.gmail.com", port, context=context) as server:
              server.login(mail, haslo)
              server.sendmail(mail, mail2, wiadomosc)

      wiadomosc_tekst =
      """\ Rozpoczęto przetwarzanie. Godzina: {1}, powiat {2}."""
      wiadomosc = wiadomosc_tekst.format(mail2, timestamp, powiat)

      wyslij(mail, mail2, wiadomosc)
Shutdown Python:
      import fme, smtplib, ssl
      from datetime import datetime
      from mail.mime.multipart import MIMEMultipart
      from mail.mime.text import MIMEText
      from mail.mime.application import MIMEApplication
      import os
      import json

      mail = fme.macroValues['mail']
      haslo = fme.macroValues['haslo']
      powiat = fme.macroValues['powiat']
      mail2 = fme.macroValues['mail2']
      data_od =  fme.macroValues['data_od']
      data_do =  fme.macroValues['data_do']
      chmury =  fme.macroValues['chmury']
      czas_zaj = str(round(fme.elapsedRunTime, 0))

      teraz = datetime.now()
      teraz_format = teraz.strftime("%d/%m/%Y %H:%M:%S")

      def wyslij(mail, mail2, wiadomosc ):
          # for SSL
          port = 465
          # SSL context
          context = ssl.create_default_context()
          with smtplib.SMTP_SSL("smtp.gmail.com", port, context=context) as server:
              server.login(mail, haslo)
              server.sendmail(mail, mail2, wiadomosc)


      def logi(powiat, data_od, data_do, chmury):
          dictionary = {
          "powiat" : powiat,
          "data_od" : data_od,
          "data_do"  : data_do,
          "chmury" : chmury
          }
          json_log = json.dumps(dictionary, indent=2)
          with open(sciezka_json, "w") as outfile:
              outfile.write(json_log)

      wiadomosc = MIMEMultipart('mixed')
      wiadomosc['From'] = 'Contact <{sender}>'.format(sender = mail)
      wiadomosc['To'] = mail2

      sciezka = powiat + r".tif"
      sciezka_dopisz = os.path.join(r"C:\Users\barte\OneDrive\Pulpit\cw11" , sciezka)
      sciezka_json = os.path.join(r"C:\Users\barte\OneDrive\Pulpit\cw11" , "log.geojson")


      status = fme.status
      if status == 0: # if there is an error
          logi(powiat, data_od, data_do, chmury)
          wiadomosc['temat'] = 'Przetwarzanie zakończone błędem!'

          wiadomosc_tekst = """
          Błąd w przetwarzaniu. Godzina: {1}""".format(mail2, teraz_format, powiat)
          tekst = MIMEText(wiadomosc_tekst, 'html')
          wiadomosc.attach(tekst)
          try:
              with open(sciezka_json, "rb") as attachment:
                  p = MIMEApplication(attachment.read(),_subtype="json")
                  p.add_header('Content-Disposition', "attachment; filename= %s" % sciezka_json.split("\\")[-1])
                  wiadomosc.attach(p)
          except Exception as e:
      	    print(str(e))

      else: # if everything is cool

          srednia =  round(fme.macroValues['mean'], 3)
          odch =  round(fme.macroValues['stdev'], 3)

          wiadomosc['temat'] = 'Przetwarzanie zakończone!'
          wiadomosc_tekst = """

          Zakończono przetwarzanie. Godzina: {1}, Powiat: {2}.
          Czas trwania działania przetwarzania: {3} s.
          Średnia: {4} Odchylenie standardowe: {5}""".format(mail2, teraz_format, powiat, czas_zaj, str(srednia), str(odch))

          tekst = MIMEText(wiadomosc_tekst, 'html')
          wiadomosc.attach(tekst)
          try:
              with open(sciezka_dopisz, "rb") as attachment:
                  p = MIMEApplication(attachment.read(),_subtype="tif")
                  p.add_header('Content-Disposition', "attachment; filename= %s" % sciezka_dopisz.split("\\")[-1])
                  wiadomosc.attach(p)
          except Exception as e:
      	    print(str(e))

      print(czas_zaj)
      tekst = MIMEText(wiadomosc_tekst, 'html')
      wyslij(mail, mail2, wiadomosc.as_string(),)

Parameters:
- chmury =
- data_do =
- data_od =
- geotiff_folder =
- haslo =
- jpeg =
- jpeg_2 =
- mail =
- mail2 =
- powiat =

Readers:
- SHAPEFILE_1: SHAPEFILE from $(FME_MF_DIR)Powiaty\Powiaty.shp
- JPEG2000_1: JPEG2000 from $(jpeg)
- JPEG2000_2: JPEG2000

Writers:
- GEOTIFF_1: GEOTIFF to $(geotiff_folder)

JPEG2000 (reader JPEG2000_1)
    -> Reprojector_1
Reprojector_1
    DEST = LL84
    INTERPOLATION_TYPE_NAME = Nearest Neighbor
    RASTER_CELL_SIZE = Preserve Cells
    RASTER_TOLERANCE = 0.0
    REPROJECTED -> NDVICalculator [Red]
JPEG2000 (reader JPEG2000_2)
    -> Reprojector_3
Reprojector_3
    DEST = LL84
    INTERPOLATION_TYPE_NAME = Nearest Neighbor
    RASTER_CELL_SIZE = Preserve Cells
    RASTER_TOLERANCE = 0.0
    REPROJECTED -> NDVICalculator [Infrared]
NDVICalculator
    COLORIZE = Blue-Yellow-Green Palette
    INDEXTYPE = NDVI
    SAVIADJUSTMENT = 0.5
    -> Reprojector_2
Reprojector_2
    DEST = LL84
    INTERPOLATION_TYPE_NAME = Nearest Neighbor
    RASTER_CELL_SIZE = Preserve Cells
    RASTER_TOLERANCE = 0.0
    REPROJECTED -> Clipper [CLIPPEE]
Powiaty (reader SHAPEFILE_1)
    attributes: JPT_SJR_KO varchar(3), JPT_KOD_JE varchar(20), JPT_NAZWA_ varchar(128), JPT_ORGAN_ varchar(254), JPT_JOR_ID long, WERSJA_OD date, WERSJA_DO date, WAZNY_OD date, WAZNY_DO date, JPT_KOD__1 varchar(3), JPT_NAZWA1 varchar(3), JPT_ORGAN1 varchar(3), JPT_WAZNA_ varchar(3), ID_BUFORA_ double, ID_BUFORA1 double, ID_TECHNIC long, IIP_PRZEST varchar(20), IIP_IDENTY varchar(128), IIP_WERSJA varchar(32), JPT_KJ_IIP varchar(20), JPT_KJ_I_1 varchar(128), JPT_KJ_I_2 varchar(32), JPT_OPIS varchar(254), JPT_SPS_KO varchar(3), ID_BUFOR_1 long, JPT_ID long, JPT_KJ_I_3 varchar(3), Shape_Leng double, Shape_Area double
    -> Tester
Tester
    BOOL_OP = OR
    COMPOSITE_TEST = 1
    TEST_CLAUSE = CASE_INSENSITIVE_TEST @Value(JPT_NAZWA_) ENDS_WITH $(powiat)
    TEST_MODE = CASE_INSENSITIVE_TEST
    PASSED -> Reprojector_4
Reprojector_4
    DEST = LL84
    INTERPOLATION_TYPE_NAME = Nearest Neighbor
    RASTER_CELL_SIZE = Preserve Cells
    RASTER_TOLERANCE = 0.0
    REPROJECTED -> Clipper [CLIPPER]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterStatisticsCalculator
RasterStatisticsCalculator
    RASTER_LEVEL = BAND_ONLY
    RASTER_STATS = "0   MEAN   STDEV  "
    -> PythonCaller
PythonCaller
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.

              """
              FME_MacroValues['mean'] = feature.getAttribute('band0.mean')
              FME_MacroValues['stdev'] = feature.getAttribute('band0.stdev')


              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> test (writer GEOTIFF_1)
test (writer GEOTIFF_1)
    attributes: JPT_SJR_KO char(3), JPT_KOD_JE char(20), JPT_NAZWA_ char(128), JPT_ORGAN_ char(254), JPT_JOR_ID integer, WERSJA_OD date, WERSJA_DO date, WAZNY_OD date, WAZNY_DO date, JPT_KOD__1 char(3), JPT_NAZWA1 char(3), JPT_ORGAN1 char(3), JPT_WAZNA_ char(3), ID_BUFORA_ float, ID_BUFORA1 float, ID_TECHNIC integer, IIP_PRZEST char(20), IIP_IDENTY char(128), IIP_WERSJA char(32), JPT_KJ_IIP char(20), JPT_KJ_I_1 char(128), JPT_KJ_I_2 char(32), JPT_OPIS char(254), JPT_SPS_KO char(3), ID_BUFOR_1 integer, JPT_ID integer, JPT_KJ_I_3 char(3), Shape_Leng float, Shape_Area float
